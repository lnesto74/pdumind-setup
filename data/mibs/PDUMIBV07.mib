--
-- PDUMIBV07.my
-- MIB generated by MG-SOFT Visual MIB Builder Version 6.0  Build 88
-- Tuesday, November 08, 2022 at 17:56:31
--

	PDUMIBV07 DEFINITIONS ::= BEGIN
 
		IMPORTS
			OBJECT-TYPE			
				FROM RFC-1212			
			TRAP-TYPE			
				FROM RFC-1215			
			enterprises			
				FROM RFC1155-SMI;
	
	
--
-- Node definitions
--
	
		-- 1.3.6.1.4.1.23280
		pdu OBJECT IDENTIFIER ::= { enterprises 23280 }

		
-- iPDU Ident Table
		-- 1.3.6.1.4.1.23280.1
		deviceStatusTableSize OBJECT-TYPE
			SYNTAX INTEGER
			ACCESS read-only
			STATUS mandatory
			DESCRIPTION
				"The total number of iPDUs"
			::= { pdu 1 }

		
		-- 1.3.6.1.4.1.23280.2
		deviceStatusTable OBJECT-TYPE
			SYNTAX SEQUENCE OF DeviceStatusEntry
			ACCESS not-accessible
			STATUS mandatory
			::= { pdu 2 }

		
		-- 1.3.6.1.4.1.23280.2.1
		deviceStatusEntry OBJECT-TYPE
			SYNTAX DeviceStatusEntry
			ACCESS not-accessible
			STATUS mandatory
			INDEX { deviceStatusIndex }
			::= { deviceStatusTable 1 }

		
		DeviceStatusEntry ::=
			SEQUENCE { 
				deviceStatusIndex
					INTEGER,
				deviceStatusVersion
					OCTET STRING,
				deviceStatusModelNumber
					OCTET STRING,
				deviceStatusSerialNumber
					OCTET STRING,
				deviceStatusActivePower
					INTEGER,
				deviceStatusReactivePower
					INTEGER,
				deviceStatusApparentPower
					INTEGER,
				deviceStatusPowerFactor
					INTEGER,
				deviceStatusActiveEnergy
					INTEGER,
				deviceStatusReactiveEnergy
					INTEGER,
				deviceStatusFrequency
					INTEGER,
				deviceStatusZeroLineCurrent
					INTEGER,
				deviceStatusThreePhaseUnbalance
					INTEGER,
				deviceStatusSummary
					OCTET STRING
			 }

		-- 1.3.6.1.4.1.23280.2.1.1
		deviceStatusIndex OBJECT-TYPE
			SYNTAX INTEGER (1..5)
			ACCESS read-only
			STATUS mandatory
			DESCRIPTION
				"The index to the PDU status table entry"
			::= { deviceStatusEntry 1 }

		
		-- 1.3.6.1.4.1.23280.2.1.2
		deviceStatusVersion OBJECT-TYPE
			SYNTAX OCTET STRING
			ACCESS read-only
			STATUS mandatory
			DESCRIPTION
				"The PDU firmware and hardware version"
			::= { deviceStatusEntry 2 }

		
		-- 1.3.6.1.4.1.23280.2.1.3
		deviceStatusModelNumber OBJECT-TYPE
			SYNTAX OCTET STRING
			ACCESS read-only
			STATUS mandatory
			DESCRIPTION
				"Device model information"
			::= { deviceStatusEntry 3 }

		
		-- 1.3.6.1.4.1.23280.2.1.4
		deviceStatusSerialNumber OBJECT-TYPE
			SYNTAX OCTET STRING
			ACCESS read-only
			STATUS mandatory
			DESCRIPTION
				"Device Serial numbers"
			::= { deviceStatusEntry 4 }

		
		-- 1.3.6.1.4.1.23280.2.1.5
		deviceStatusActivePower OBJECT-TYPE
			SYNTAX INTEGER
			ACCESS read-only
			STATUS mandatory
			DESCRIPTION
				"Models that do not support this feature, 
				will respond to this OID with a value of 
				notSupported (-1).
				Indicates the PDU Active Power. Units:1 Watt"
			::= { deviceStatusEntry 5 }

		
		-- 1.3.6.1.4.1.23280.2.1.6
		deviceStatusReactivePower OBJECT-TYPE
			SYNTAX INTEGER
			ACCESS read-only
			STATUS mandatory
			DESCRIPTION
				"Models that do not support this feature, 
				will respond to this OID with a value of 
				notSupported (-1).
				Indicates the PDU Reactive Power. Units:1 Var"
			::= { deviceStatusEntry 6 }

		
		-- 1.3.6.1.4.1.23280.2.1.7
		deviceStatusApparentPower OBJECT-TYPE
			SYNTAX INTEGER
			ACCESS read-only
			STATUS mandatory
			DESCRIPTION
				"Models that do not support this feature, 
				will respond to this OID with a value of 
				notSupported (-1).
				Indicates the PDU Apparent Power. Units:1 VA"
			::= { deviceStatusEntry 7 }

		
		-- 1.3.6.1.4.1.23280.2.1.8
		deviceStatusPowerFactor OBJECT-TYPE
			SYNTAX INTEGER
			ACCESS read-only
			STATUS mandatory
			DESCRIPTION
				"Models that do not support this feature, 
				will respond to this OID with a value of 
				notSupported (-1).
				Indicates the PDU Power Factor. Units:0.1%"
			::= { deviceStatusEntry 8 }

		
		-- 1.3.6.1.4.1.23280.2.1.9
		deviceStatusActiveEnergy OBJECT-TYPE
			SYNTAX INTEGER
			ACCESS read-only
			STATUS mandatory
			DESCRIPTION
				"Models that do not support this feature, 
				will respond to this OID with a value of 
				notSupported (-1).
				Indicates the PDU Active Energy. Units:1 Wh"
			::= { deviceStatusEntry 9 }

		
		-- 1.3.6.1.4.1.23280.2.1.10
		deviceStatusReactiveEnergy OBJECT-TYPE
			SYNTAX INTEGER
			ACCESS read-only
			STATUS mandatory
			DESCRIPTION
				"Models that do not support this feature, 
				will respond to this OID with a value of 
				notSupported (-1).
				Indicates the PDU Active Energy. Units:1 Varh"
			::= { deviceStatusEntry 10 }

		
		-- 1.3.6.1.4.1.23280.2.1.11
		deviceStatusFrequency OBJECT-TYPE
			SYNTAX INTEGER
			ACCESS read-only
			STATUS mandatory
			DESCRIPTION
				"Models that do not support this feature, 
				will respond to this OID with a value of 
				notSupported (-1).
				Indicates the PDU Frequency. Units:0.001 Hz"
			::= { deviceStatusEntry 11 }

		
		-- 1.3.6.1.4.1.23280.2.1.12
		deviceStatusZeroLineCurrent OBJECT-TYPE
			SYNTAX INTEGER
			ACCESS read-only
			STATUS mandatory
			DESCRIPTION
				"Models that do not support this feature, 
				will respond to this OID with a value of 
				notSupported (-1).
				Indicates the Three phase PDU Zero line current. 
				Units:0.01 A"
			::= { deviceStatusEntry 12 }

		
		-- 1.3.6.1.4.1.23280.2.1.13
		deviceStatusThreePhaseUnbalance OBJECT-TYPE
			SYNTAX INTEGER
			ACCESS read-only
			STATUS mandatory
			DESCRIPTION
				"Models that do not support this feature, 
				will respond to this OID with a value of 
				notSupported (-1).
				Indicates the Three phase PDU percentage 
				of three-phase unbalance. Units:1%"
			::= { deviceStatusEntry 13 }

		
		-- 1.3.6.1.4.1.23280.2.1.14
		deviceStatusSummary OBJECT-TYPE
			SYNTAX OCTET STRING
			ACCESS read-only
			STATUS mandatory
			::= { deviceStatusEntry 14 }

		
		-- 1.3.6.1.4.1.23280.3
		deviceControlTable OBJECT-TYPE
			SYNTAX SEQUENCE OF DeviceControlEntry
			ACCESS not-accessible
			STATUS mandatory
			::= { pdu 3 }

		
		-- 1.3.6.1.4.1.23280.3.1
		deviceControlEntry OBJECT-TYPE
			SYNTAX DeviceControlEntry
			ACCESS not-accessible
			STATUS mandatory
			INDEX { deviceStatusIndex }
			::= { deviceControlTable 1 }

		
		DeviceControlEntry ::=
			SEQUENCE { 
				deviceControlIndex
					INTEGER,
				deviceControlReboot
					INTEGER,
				deviceControlEngeryReset
					INTEGER,
				deviceControlBeepAlarm
					INTEGER,
				deviceControlZeroLineCurrentMaxThreshold
					INTEGER,
				deviceControlThreePhaseUnbalanceMaxThreshold
					INTEGER
			 }

		-- 1.3.6.1.4.1.23280.3.1.1
		deviceControlIndex OBJECT-TYPE
			SYNTAX INTEGER (1..5)
			ACCESS read-only
			STATUS mandatory
			DESCRIPTION
				"The index to the PDU control table entry"
			::= { deviceControlEntry 1 }

		
		-- 1.3.6.1.4.1.23280.3.1.2
		deviceControlReboot OBJECT-TYPE
			SYNTAX INTEGER
				{
				reboot(1),
				noOperation(2)
				}
			ACCESS read-write
			STATUS mandatory
			DESCRIPTION
				"Setting this OID to reboot (1) will cause 
				the device reboot immediately.
				Getting this OID in models that support this 
				feature will do nothing and return the 
				noOperation(2) value."
			::= { deviceControlEntry 2 }

		
		-- 1.3.6.1.4.1.23280.3.1.3
		deviceControlEngeryReset OBJECT-TYPE
			SYNTAX INTEGER
				{
				reset(1),
				noOperation(2)
				}
			ACCESS read-write
			STATUS mandatory
			DESCRIPTION
				"Setting this OID to EnergyReset(1) will cause 
				the electrical energy data of the device to be 
				cleared immediately.
				Getting this OID in models that support this 
				feature will do nothing and return the 
				noOperation(2) value."
			::= { deviceControlEntry 3 }

		
		-- 1.3.6.1.4.1.23280.3.1.4
		deviceControlBeepAlarm OBJECT-TYPE
			SYNTAX INTEGER
				{
				off(1),
				on(2)
				}
			ACCESS read-write
			STATUS mandatory
			DESCRIPTION
				"User-defined Beep alarm, 1 for turn off Beep, 2 for turn on Beep.
				Models that do not support this feature will respond to this OID
				with a value of -1."
			::= { deviceControlEntry 4 }

		
		-- 1.3.6.1.4.1.23280.3.1.5
		deviceControlZeroLineCurrentMaxThreshold OBJECT-TYPE
			SYNTAX INTEGER (0..100)
			ACCESS read-write
			STATUS mandatory
			DESCRIPTION
				"User-defined Three Phase PDU Max Zero Line Current alarm threshold. 
				Models that do not support this feature will
				respond to this OID with a value of -1.
				Units: 0.01 A"
			::= { deviceControlEntry 5 }

		
		-- 1.3.6.1.4.1.23280.3.1.6
		deviceControlThreePhaseUnbalanceMaxThreshold OBJECT-TYPE
			SYNTAX INTEGER
			ACCESS read-write
			STATUS mandatory
			DESCRIPTION
				"User-defined Three Phase PDU Max percentage 
				of three-phase unbalance alarm threshold. 
				Models that do not support this feature will
				respond to this OID with a value of -1.
				Units: 1%"
			::= { deviceControlEntry 6 }

		
-- ePDU Phase Data
		-- 1.3.6.1.4.1.23280.4
		phaseTableSize OBJECT-TYPE
			SYNTAX INTEGER
			ACCESS read-only
			STATUS mandatory
			DESCRIPTION
				"The number of connected PDU phases"
			::= { pdu 4 }

		
		-- 1.3.6.1.4.1.23280.5
		phaseConfigTable OBJECT-TYPE
			SYNTAX SEQUENCE OF PhaseConfigEntry
			ACCESS not-accessible
			STATUS mandatory
			::= { pdu 5 }

		
		-- 1.3.6.1.4.1.23280.5.1
		phaseConfigEntry OBJECT-TYPE
			SYNTAX PhaseConfigEntry
			ACCESS not-accessible
			STATUS mandatory
			INDEX { deviceStatusIndex }
			::= { phaseConfigTable 1 }

		
		PhaseConfigEntry ::=
			SEQUENCE { 
				phaseConfigIndex
					INTEGER,
				phaseConfigOverVoltageThreshold
					INTEGER,
				phaseConfigLowVoltageThreshold
					INTEGER,
				phaseConfigOverCurrentThreshold
					INTEGER,
				phaseConfigLowCurrentThreshold
					INTEGER
			 }

		-- 1.3.6.1.4.1.23280.5.1.1
		phaseConfigIndex OBJECT-TYPE
			SYNTAX INTEGER (1..15)
			ACCESS read-only
			STATUS mandatory
			DESCRIPTION
				"The index to the PDU phase configuration
				table entry"
			::= { phaseConfigEntry 1 }

		
		-- 1.3.6.1.4.1.23280.5.1.2
		phaseConfigOverVoltageThreshold OBJECT-TYPE
			SYNTAX INTEGER (0..5000)
			ACCESS read-write
			STATUS mandatory
			DESCRIPTION
				"User-defined Phase Over Voltage alarm threshold. 
				Models that do not support this feature will
				respond to this OID with a value of -1.
				Units:0.1 V"
			::= { phaseConfigEntry 2 }

		
		-- 1.3.6.1.4.1.23280.5.1.3
		phaseConfigLowVoltageThreshold OBJECT-TYPE
			SYNTAX INTEGER (0..5000)
			ACCESS read-write
			STATUS mandatory
			DESCRIPTION
				"User-defined Phase Low Voltage alarm threshold. 
				Models that do not support this feature will
				respond to this OID with a value of -1.
				Units:0.1 V"
			::= { phaseConfigEntry 3 }

		
		-- 1.3.6.1.4.1.23280.5.1.4
		phaseConfigOverCurrentThreshold OBJECT-TYPE
			SYNTAX INTEGER (0..9999)
			ACCESS read-write
			STATUS mandatory
			DESCRIPTION
				"User-defined Phase Over Current alarm threshold. 
				Models that do not support this feature will
				respond to this OID with a value of -1.
				Units:0.01 A"
			::= { phaseConfigEntry 4 }

		
		-- 1.3.6.1.4.1.23280.5.1.5
		phaseConfigLowCurrentThreshold OBJECT-TYPE
			SYNTAX INTEGER (0..9999)
			ACCESS read-write
			STATUS mandatory
			DESCRIPTION
				"User-defined Phase Low Current alarm threshold. 
				Models that do not support this feature will
				respond to this OID with a value of -1.
				Units:0.01 A"
			::= { phaseConfigEntry 5 }

		
		-- 1.3.6.1.4.1.23280.6
		phaseStatusTable OBJECT-TYPE
			SYNTAX SEQUENCE OF PhaseStatusEntry
			ACCESS not-accessible
			STATUS mandatory
			::= { pdu 6 }

		
		-- 1.3.6.1.4.1.23280.6.1
		phaseStatusEntry OBJECT-TYPE
			SYNTAX PhaseStatusEntry
			ACCESS not-accessible
			STATUS mandatory
			INDEX { deviceStatusIndex }
			::= { phaseStatusTable 1 }

		
		PhaseStatusEntry ::=
			SEQUENCE { 
				phaseStatusIndex
					INTEGER,
				phaseStatusVoltage
					INTEGER,
				phaseStatusCurrent
					INTEGER,
				phaseStatusActivePower
					INTEGER,
				phaseStatusReactivePower
					INTEGER,
				phaseStatusApparentPower
					INTEGER,
				phaseStatusPowerFactor
					INTEGER,
				phaseStatusActiveEnergy
					INTEGER,
				phaseStatusReactiveEnergy
					INTEGER,
				phaseStatusVoltageLimitState
					INTEGER,
				phaseStatusCurrentLimitState
					INTEGER
			 }

		-- 1.3.6.1.4.1.23280.6.1.1
		phaseStatusIndex OBJECT-TYPE
			SYNTAX INTEGER (1..15)
			ACCESS read-only
			STATUS mandatory
			DESCRIPTION
				"The index to the PDU phase configuration
				table entry"
			::= { phaseStatusEntry 1 }

		
		-- 1.3.6.1.4.1.23280.6.1.2
		phaseStatusVoltage OBJECT-TYPE
			SYNTAX INTEGER
			ACCESS read-only
			STATUS mandatory
			DESCRIPTION
				"Indicates the Phase Voltage. Units:0.1 V"
			::= { phaseStatusEntry 2 }

		
		-- 1.3.6.1.4.1.23280.6.1.3
		phaseStatusCurrent OBJECT-TYPE
			SYNTAX INTEGER
			ACCESS read-only
			STATUS mandatory
			DESCRIPTION
				"Indicates the Phase Current. Units:0.01 A"
			::= { phaseStatusEntry 3 }

		
		-- 1.3.6.1.4.1.23280.6.1.4
		phaseStatusActivePower OBJECT-TYPE
			SYNTAX INTEGER
			ACCESS read-only
			STATUS mandatory
			DESCRIPTION
				"Indicates the Phase Active Power. Units:1 Watt"
			::= { phaseStatusEntry 4 }

		
		-- 1.3.6.1.4.1.23280.6.1.5
		phaseStatusReactivePower OBJECT-TYPE
			SYNTAX INTEGER
			ACCESS read-only
			STATUS mandatory
			DESCRIPTION
				"Models that do not support this feature, 
				will respond to this OID with a value of 
				notSupported (-1).
				Indicates the Phase Reactive Power. Units:1 Var"
			::= { phaseStatusEntry 5 }

		
		-- 1.3.6.1.4.1.23280.6.1.6
		phaseStatusApparentPower OBJECT-TYPE
			SYNTAX INTEGER
			ACCESS read-only
			STATUS mandatory
			DESCRIPTION
				"Models that do not support this feature, 
				will respond to this OID with a value of 
				notSupported (-1).
				Indicates the Phase Apparent Power. Units:1 VA"
			::= { phaseStatusEntry 6 }

		
		-- 1.3.6.1.4.1.23280.6.1.7
		phaseStatusPowerFactor OBJECT-TYPE
			SYNTAX INTEGER
			ACCESS read-only
			STATUS mandatory
			DESCRIPTION
				"Indicates the Phase Power Factor. Units:0.1%"
			::= { phaseStatusEntry 7 }

		
		-- 1.3.6.1.4.1.23280.6.1.8
		phaseStatusActiveEnergy OBJECT-TYPE
			SYNTAX INTEGER
			ACCESS read-only
			STATUS mandatory
			DESCRIPTION
				"Indicates the Phase Active Energy. Units:1 Wh"
			::= { phaseStatusEntry 8 }

		
		-- 1.3.6.1.4.1.23280.6.1.9
		phaseStatusReactiveEnergy OBJECT-TYPE
			SYNTAX INTEGER
			ACCESS read-only
			STATUS mandatory
			DESCRIPTION
				"Models that do not support this feature, 
				will respond to this OID with a value of 
				notSupported (-1).
				Indicates the Phase Reactive Energy. Units:1 Varh"
			::= { phaseStatusEntry 9 }

		
		-- 1.3.6.1.4.1.23280.6.1.10
		phaseStatusVoltageLimitState OBJECT-TYPE
			SYNTAX INTEGER
				{
				normal(1),
				upperLimit(2),
				lowerLimit(3)
				}
			ACCESS read-only
			STATUS mandatory
			DESCRIPTION
				"Indicates the Phase Voltage limit state.
				Normal(1) means that the limit is not exceeded. 
				upperLimit(2) is the upper limit, 
				and lowerLimit(3) is the lower limit."
			::= { phaseStatusEntry 10 }

		
		-- 1.3.6.1.4.1.23280.6.1.11
		phaseStatusCurrentLimitState OBJECT-TYPE
			SYNTAX INTEGER
				{
				normal(1),
				upperLimit(2),
				lowerLimit(3)
				}
			ACCESS read-only
			STATUS mandatory
			DESCRIPTION
				"Indicates the Phase Current limit state.
				Normal(1) means that the limit is not exceeded. 
				upperLimit(2) is the upper limit, 
				and lowerLimit(3) is the lower limit."
			::= { phaseStatusEntry 11 }

		
-- ePDU Switched Outlet Data
		-- 1.3.6.1.4.1.23280.7
		outletTableSize OBJECT-TYPE
			SYNTAX INTEGER
			ACCESS read-only
			STATUS mandatory
			DESCRIPTION
				"The number of switched outlets on connected PDUs."
			::= { pdu 7 }

		
		-- 1.3.6.1.4.1.23280.8
		outletStatusTable OBJECT-TYPE
			SYNTAX SEQUENCE OF OutletStatusEntry
			ACCESS not-accessible
			STATUS mandatory
			::= { pdu 8 }

		
		-- 1.3.6.1.4.1.23280.8.1
		outletStatusEntry OBJECT-TYPE
			SYNTAX OutletStatusEntry
			ACCESS not-accessible
			STATUS mandatory
			INDEX { deviceStatusIndex }
			::= { outletStatusTable 1 }

		
		OutletStatusEntry ::=
			SEQUENCE { 
				outletStatusIndex
					INTEGER,
				outletStatusState
					INTEGER,
				outletStatusVoltage
					INTEGER,
				outletStatusCurrent
					INTEGER,
				outletStatusActivePower
					INTEGER,
				outletStatusPowerFactor
					INTEGER,
				outletStatusActiveEnergy
					INTEGER
			 }

		-- 1.3.6.1.4.1.23280.8.1.1
		outletStatusIndex OBJECT-TYPE
			SYNTAX INTEGER (1..120)
			ACCESS read-only
			STATUS mandatory
			DESCRIPTION
				"The index to the PDU switched outlet
				status information table entry.
				Models that do not support this feature, 
				will respond to this OID with a value of 
				notSupported (-1)."
			::= { outletStatusEntry 1 }

		
		-- 1.3.6.1.4.1.23280.8.1.2
		outletStatusState OBJECT-TYPE
			SYNTAX INTEGER
				{
				off(1),
				on(2)
				}
			ACCESS read-only
			STATUS mandatory
			DESCRIPTION
				"Indicates the present switch state of the 
				PDU switched outlet being queried.
				Models that do not support this feature, 
				will respond to this OID with a value of 
				notSupported (-1)."
			::= { outletStatusEntry 2 }

		
		-- 1.3.6.1.4.1.23280.8.1.3
		outletStatusVoltage OBJECT-TYPE
			SYNTAX INTEGER
			ACCESS read-only
			STATUS mandatory
			DESCRIPTION
				"Indicates the Outlet Voltage. Units:0.1 V.
				Models that do not support this feature, 
				will respond to this OID with a value of 
				notSupported (-1).
				"
			::= { outletStatusEntry 3 }

		
		-- 1.3.6.1.4.1.23280.8.1.4
		outletStatusCurrent OBJECT-TYPE
			SYNTAX INTEGER
			ACCESS read-only
			STATUS mandatory
			DESCRIPTION
				"Indicates the Outlet Current. Units:0.01 A.
				Models that do not support this feature, 
				will respond to this OID with a value of 
				notSupported (-1)."
			::= { outletStatusEntry 4 }

		
		-- 1.3.6.1.4.1.23280.8.1.5
		outletStatusActivePower OBJECT-TYPE
			SYNTAX INTEGER
			ACCESS read-only
			STATUS mandatory
			DESCRIPTION
				"Indicates the Outlet Active Power. Units:1 Watt.
				Models that do not support this feature, 
				will respond to this OID with a value of 
				notSupported (-1)."
			::= { outletStatusEntry 5 }

		
		-- 1.3.6.1.4.1.23280.8.1.6
		outletStatusPowerFactor OBJECT-TYPE
			SYNTAX INTEGER
			ACCESS read-only
			STATUS mandatory
			DESCRIPTION
				"Models that do not support this feature, 
				will respond to this OID with a value of 
				notSupported (-1).
				Indicates the Outlet Power Factor. Units:0.1%"
			::= { outletStatusEntry 6 }

		
		-- 1.3.6.1.4.1.23280.8.1.7
		outletStatusActiveEnergy OBJECT-TYPE
			SYNTAX INTEGER
			ACCESS read-only
			STATUS mandatory
			DESCRIPTION
				"Indicates the Outlet Energy. Units:1 Wh.
				Models that do not support this feature, 
				will respond to this OID with a value of 
				notSupported (-1)."
			::= { outletStatusEntry 7 }

		
		-- 1.3.6.1.4.1.23280.9
		outletControlTable OBJECT-TYPE
			SYNTAX SEQUENCE OF OutletControlEntry
			ACCESS not-accessible
			STATUS mandatory
			::= { pdu 9 }

		
		-- 1.3.6.1.4.1.23280.9.1
		outletControlEntry OBJECT-TYPE
			SYNTAX OutletControlEntry
			ACCESS not-accessible
			STATUS mandatory
			INDEX { deviceStatusIndex }
			::= { outletControlTable 1 }

		
		OutletControlEntry ::=
			SEQUENCE { 
				outletControlIndex
					INTEGER,
				outletControlCommand
					INTEGER,
				outletControlEnergyReset
					INTEGER
			 }

		-- 1.3.6.1.4.1.23280.9.1.1
		outletControlIndex OBJECT-TYPE
			SYNTAX INTEGER (1..120)
			ACCESS read-only
			STATUS mandatory
			DESCRIPTION
				"The index to the PDU switched outlet
				status information table entry.
				Models that do not support this feature, 
				will respond to this OID with a value of 
				notSupported (-1)."
			::= { outletControlEntry 1 }

		
		-- 1.3.6.1.4.1.23280.9.1.2
		outletControlCommand OBJECT-TYPE
			SYNTAX INTEGER
				{
				on(1),
				off(2),
				reboot(3),
				unknown(4)
				}
			ACCESS read-write
			STATUS mandatory
			DESCRIPTION
				"Getting this variable will return the outlet state. If
				the outlet is on, the On (1) value will be returned.
				If the outlet is off, the Off (2) value will be
				returned. If the state of the outlet cannot be
				determined, the Unknown (3) value will be returned.
				If the outletUnknown condition should occur, all devices
				powered by the PDU should be shut down. The PDU's power
				should then be cycled to clear this condition.
				Models that do not support this feature, 
				will respond to this OID with a value of 
				notSupported (-1).
				
				Setting this variable to On (1) will immediately turn
				the outlet on.
				
				Setting this variable to Off (2) will immediately turn
				the outlet off."
			::= { outletControlEntry 2 }

		
		-- 1.3.6.1.4.1.23280.9.1.3
		outletControlEnergyReset OBJECT-TYPE
			SYNTAX INTEGER
				{
				reset(1),
				noOperation(2)
				}
			ACCESS read-write
			STATUS mandatory
			DESCRIPTION
				"Setting this OID to EnergyReset(1) will cause 
				the electrical energy data of the device to be 
				cleared immediately.
				Getting this OID in models that support this 
				feature will do nothing and return the 
				noOperation(2) value.
				Models that do not support this feature, 
				will respond to this OID with a value of 
				notSupported (-1).
				"
			::= { outletControlEntry 3 }

		
-- ePDU Temperature and Humidity Sensor Data
		-- 1.3.6.1.4.1.23280.10
		sensorTableSize OBJECT-TYPE
			SYNTAX INTEGER
			ACCESS read-only
			STATUS mandatory
			DESCRIPTION
				"The number of connected sensors"
			::= { pdu 10 }

		
		-- 1.3.6.1.4.1.23280.11
		sensorConfigTable OBJECT-TYPE
			SYNTAX SEQUENCE OF SensorConfigEntry
			ACCESS not-accessible
			STATUS mandatory
			::= { pdu 11 }

		
		-- 1.3.6.1.4.1.23280.11.1
		sensorConfigEntry OBJECT-TYPE
			SYNTAX SensorConfigEntry
			ACCESS not-accessible
			STATUS mandatory
			INDEX { sensorConfigIndex }
			::= { sensorConfigTable 1 }

		
		SensorConfigEntry ::=
			SEQUENCE { 
				sensorConfigIndex
					INTEGER,
				sensorConfigTempMaxThreshold
					INTEGER,
				sensorConfigTempMinThreshold
					INTEGER,
				sensorConfigHumidityMaxThreshold
					INTEGER,
				sensorConfigHumidityMinThreshold
					INTEGER
			 }

		-- 1.3.6.1.4.1.23280.11.1.1
		sensorConfigIndex OBJECT-TYPE
			SYNTAX INTEGER (1..4)
			ACCESS read-only
			STATUS mandatory
			DESCRIPTION
				"The index to the sensor
				configuration data table entry"
			::= { sensorConfigEntry 1 }

		
		-- 1.3.6.1.4.1.23280.11.1.2
		sensorConfigTempMaxThreshold OBJECT-TYPE
			SYNTAX INTEGER (0..1000)
			ACCESS read-write
			STATUS mandatory
			DESCRIPTION
				"User-defined Max Temperature alarm threshold. 
				Models that do not support this feature will
				respond to this OID with a value of -1.
				Units: 0.1   "
			::= { sensorConfigEntry 2 }

		
		-- 1.3.6.1.4.1.23280.11.1.3
		sensorConfigTempMinThreshold OBJECT-TYPE
			SYNTAX INTEGER (0..1000)
			ACCESS read-write
			STATUS mandatory
			DESCRIPTION
				"User-defined Min Temperature alarm threshold. 
				Models that do not support this feature will
				respond to this OID with a value of -1.
				Units: 0.1   "
			::= { sensorConfigEntry 3 }

		
		-- 1.3.6.1.4.1.23280.11.1.4
		sensorConfigHumidityMaxThreshold OBJECT-TYPE
			SYNTAX INTEGER (0..1000)
			ACCESS read-write
			STATUS mandatory
			DESCRIPTION
				"User-defined Max Humidity alarm threshold. 
				Models that do not support this feature will
				respond to this OID with a value of -1.
				Units: 0.1% RH"
			::= { sensorConfigEntry 4 }

		
		-- 1.3.6.1.4.1.23280.11.1.5
		sensorConfigHumidityMinThreshold OBJECT-TYPE
			SYNTAX INTEGER (0..1000)
			ACCESS read-write
			STATUS mandatory
			DESCRIPTION
				"User-defined Min Humidity alarm threshold. 
				Models that do not support this feature will
				respond to this OID with a value of -1.
				Units: 0.1% RH"
			::= { sensorConfigEntry 5 }

		
		-- 1.3.6.1.4.1.23280.12
		sensorStatusTable OBJECT-TYPE
			SYNTAX SEQUENCE OF SensorStatusEntry
			ACCESS not-accessible
			STATUS mandatory
			::= { pdu 12 }

		
		-- 1.3.6.1.4.1.23280.12.1
		sensorStatusEntry OBJECT-TYPE
			SYNTAX SensorStatusEntry
			ACCESS not-accessible
			STATUS mandatory
			INDEX { deviceStatusIndex }
			::= { sensorStatusTable 1 }

		
		SensorStatusEntry ::=
			SEQUENCE { 
				sensorStatusIndex
					INTEGER,
				sensorStatusTemperature
					INTEGER,
				sensorStatusHumidity
					INTEGER,
				sensorStatusTemperatureLimitState
					INTEGER,
				sensorStatusHumidityLimitState
					INTEGER,
				sensorStatusIOSensorState
					INTEGER
			 }

		-- 1.3.6.1.4.1.23280.12.1.1
		sensorStatusIndex OBJECT-TYPE
			SYNTAX INTEGER (1..4)
			ACCESS read-only
			STATUS mandatory
			DESCRIPTION
				"The index to the sensor status data 
				table entry"
			::= { sensorStatusEntry 1 }

		sensorStatusTemperature OBJECT-TYPE
			SYNTAX INTEGER
			ACCESS read-only
			STATUS mandatory
			DESCRIPTION
				"Sensor temperature reading in tenths of degrees Celsius. Units:0.1   "
			::= { sensorStatusEntry 2 }

		-- 1.3.6.1.4.1.23280.12.1.2
		sensorTemperature1 OBJECT-TYPE
			SYNTAX INTEGER
			ACCESS read-only
			STATUS mandatory
			DESCRIPTION
				"Sensor temperature reading in tenths of degrees Celsius. Units:0.1   "
			::= { sensorStatusTemperature 1 }

		sensorTemperature2 OBJECT-TYPE
			SYNTAX INTEGER
			ACCESS read-only
			STATUS mandatory
			DESCRIPTION
				"Sensor temperature reading in tenths of degrees Celsius. Units:0.1   "
			::= { sensorStatusTemperature 2 }

		sensorTemperature3 OBJECT-TYPE
			SYNTAX INTEGER
			ACCESS read-only
			STATUS mandatory
			DESCRIPTION
				"Sensor temperature reading in tenths of degrees Celsius. Units:0.1   "
			::= { sensorStatusTemperature 3 }

		sensorTemperature4 OBJECT-TYPE
			SYNTAX INTEGER
			ACCESS read-only
			STATUS mandatory
			DESCRIPTION
				"Sensor temperature reading in tenths of degrees Celsius. Units:0.1   "
			::= { sensorStatusTemperature 4 }

		sensorTemperature5 OBJECT-TYPE
			SYNTAX INTEGER
			ACCESS read-only
			STATUS mandatory
			DESCRIPTION
				"Sensor temperature reading in tenths of degrees Celsius. Units:0.1   "
			::= { sensorStatusTemperature 5 }

		sensorTemperature6 OBJECT-TYPE
			SYNTAX INTEGER
			ACCESS read-only
			STATUS mandatory
			DESCRIPTION
				"Sensor temperature reading in tenths of degrees Celsius. Units:0.1   "
			::= { sensorStatusTemperature 6 }

		sensorTemperature7 OBJECT-TYPE
			SYNTAX INTEGER
			ACCESS read-only
			STATUS mandatory
			DESCRIPTION
				"Sensor temperature reading in tenths of degrees Celsius. Units:0.1   "
			::= { sensorStatusTemperature 7 }

		sensorTemperature8 OBJECT-TYPE
			SYNTAX INTEGER
			ACCESS read-only
			STATUS mandatory
			DESCRIPTION
				"Sensor temperature reading in tenths of degrees Celsius. Units:0.1   "
			::= { sensorStatusTemperature 8 }

		sensorTemperature9 OBJECT-TYPE
			SYNTAX INTEGER
			ACCESS read-only
			STATUS mandatory
			DESCRIPTION
				"Sensor temperature reading in tenths of degrees Celsius. Units:0.1   "
			::= { sensorStatusTemperature 9 }

		sensorTemperature10 OBJECT-TYPE
			SYNTAX INTEGER
			ACCESS read-only
			STATUS mandatory
			DESCRIPTION
				"Sensor temperature reading in tenths of degrees Celsius. Units:0.1   "
			::= { sensorStatusTemperature 10 }

		sensorTemperature11 OBJECT-TYPE
			SYNTAX INTEGER
			ACCESS read-only
			STATUS mandatory
			DESCRIPTION
				"Sensor temperature reading in tenths of degrees Celsius. Units:0.1   "
			::= { sensorStatusTemperature 11 }

		sensorTemperature12 OBJECT-TYPE
			SYNTAX INTEGER
			ACCESS read-only
			STATUS mandatory
			DESCRIPTION
				"Sensor temperature reading in tenths of degrees Celsius. Units:0.1   "
			::= { sensorStatusTemperature 12 }

		sensorTemperature13 OBJECT-TYPE
			SYNTAX INTEGER
			ACCESS read-only
			STATUS mandatory
			DESCRIPTION
				"Sensor temperature reading in tenths of degrees Celsius. Units:0.1   "
			::= { sensorStatusTemperature 13 }

		sensorTemperature14 OBJECT-TYPE
			SYNTAX INTEGER
			ACCESS read-only
			STATUS mandatory
			DESCRIPTION
				"Sensor temperature reading in tenths of degrees Celsius. Units:0.1   "
			::= { sensorStatusTemperature 14 }

		sensorTemperature15 OBJECT-TYPE
			SYNTAX INTEGER
			ACCESS read-only
			STATUS mandatory
			DESCRIPTION
				"Sensor temperature reading in tenths of degrees Celsius. Units:0.1   "
			::= { sensorStatusTemperature 15 }

		sensorTemperature16 OBJECT-TYPE
			SYNTAX INTEGER
			ACCESS read-only
			STATUS mandatory
			DESCRIPTION
				"Sensor temperature reading in tenths of degrees Celsius. Units:0.1   "
			::= { sensorStatusTemperature 16 }

		sensorTemperature17 OBJECT-TYPE
			SYNTAX INTEGER
			ACCESS read-only
			STATUS mandatory
			DESCRIPTION
				"Sensor temperature reading in tenths of degrees Celsius. Units:0.1   "
			::= { sensorStatusTemperature 17 }

		sensorTemperature18 OBJECT-TYPE
			SYNTAX INTEGER
			ACCESS read-only
			STATUS mandatory
			DESCRIPTION
				"Sensor temperature reading in tenths of degrees Celsius. Units:0.1   "
			::= { sensorStatusTemperature 18 }

		sensorTemperature19 OBJECT-TYPE
			SYNTAX INTEGER
			ACCESS read-only
			STATUS mandatory
			DESCRIPTION
				"Sensor temperature reading in tenths of degrees Celsius. Units:0.1   "
			::= { sensorStatusTemperature 19 }

		sensorTemperature20 OBJECT-TYPE
			SYNTAX INTEGER
			ACCESS read-only
			STATUS mandatory
			DESCRIPTION
				"Sensor temperature reading in tenths of degrees Celsius. Units:0.1   "
			::= { sensorStatusTemperature 20 }

		sensorTemperature21 OBJECT-TYPE
			SYNTAX INTEGER
			ACCESS read-only
			STATUS mandatory
			DESCRIPTION
				"Sensor temperature reading in tenths of degrees Celsius. Units:0.1   "
			::= { sensorStatusTemperature 21 }

		sensorTemperature22 OBJECT-TYPE
			SYNTAX INTEGER
			ACCESS read-only
			STATUS mandatory
			DESCRIPTION
				"Sensor temperature reading in tenths of degrees Celsius. Units:0.1   "
			::= { sensorStatusTemperature 22 }

		sensorTemperature23 OBJECT-TYPE
			SYNTAX INTEGER
			ACCESS read-only
			STATUS mandatory
			DESCRIPTION
				"Sensor temperature reading in tenths of degrees Celsius. Units:0.1   "
			::= { sensorStatusTemperature 23 }

		sensorTemperature24 OBJECT-TYPE
			SYNTAX INTEGER
			ACCESS read-only
			STATUS mandatory
			DESCRIPTION
				"Sensor temperature reading in tenths of degrees Celsius. Units:0.1   "
			::= { sensorStatusTemperature 24 }

		sensorTemperature25 OBJECT-TYPE
			SYNTAX INTEGER
			ACCESS read-only
			STATUS mandatory
			DESCRIPTION
				"Sensor temperature reading in tenths of degrees Celsius. Units:0.1   "
			::= { sensorStatusTemperature 25 }

		sensorTemperature26 OBJECT-TYPE
			SYNTAX INTEGER
			ACCESS read-only
			STATUS mandatory
			DESCRIPTION
				"Sensor temperature reading in tenths of degrees Celsius. Units:0.1   "
			::= { sensorStatusTemperature 26 }

		sensorTemperature27 OBJECT-TYPE
			SYNTAX INTEGER
			ACCESS read-only
			STATUS mandatory
			DESCRIPTION
				"Sensor temperature reading in tenths of degrees Celsius. Units:0.1   "
			::= { sensorStatusTemperature 27 }

		sensorTemperature28 OBJECT-TYPE
			SYNTAX INTEGER
			ACCESS read-only
			STATUS mandatory
			DESCRIPTION
				"Sensor temperature reading in tenths of degrees Celsius. Units:0.1   "
			::= { sensorStatusTemperature 28 }

		sensorTemperature29 OBJECT-TYPE
			SYNTAX INTEGER
			ACCESS read-only
			STATUS mandatory
			DESCRIPTION
				"Sensor temperature reading in tenths of degrees Celsius. Units:0.1   "
			::= { sensorStatusTemperature 29 }

		sensorTemperature30 OBJECT-TYPE
			SYNTAX INTEGER
			ACCESS read-only
			STATUS mandatory
			DESCRIPTION
				"Sensor temperature reading in tenths of degrees Celsius. Units:0.1   "
			::= { sensorStatusTemperature 30 }

		sensorTemperature31 OBJECT-TYPE
			SYNTAX INTEGER
			ACCESS read-only
			STATUS mandatory
			DESCRIPTION
				"Sensor temperature reading in tenths of degrees Celsius. Units:0.1   "
			::= { sensorStatusTemperature 31 }

		sensorTemperature32 OBJECT-TYPE
			SYNTAX INTEGER
			ACCESS read-only
			STATUS mandatory
			DESCRIPTION
				"Sensor temperature reading in tenths of degrees Celsius. Units:0.1   "
			::= { sensorStatusTemperature 32 }

		sensorTemperature33 OBJECT-TYPE
			SYNTAX INTEGER
			ACCESS read-only
			STATUS mandatory
			DESCRIPTION
				"Sensor temperature reading in tenths of degrees Celsius. Units:0.1   "
			::= { sensorStatusTemperature 33 }

		sensorTemperature34 OBJECT-TYPE
			SYNTAX INTEGER
			ACCESS read-only
			STATUS mandatory
			DESCRIPTION
				"Sensor temperature reading in tenths of degrees Celsius. Units:0.1   "
			::= { sensorStatusTemperature 34 }

		sensorTemperature35 OBJECT-TYPE
			SYNTAX INTEGER
			ACCESS read-only
			STATUS mandatory
			DESCRIPTION
				"Sensor temperature reading in tenths of degrees Celsius. Units:0.1   "
			::= { sensorStatusTemperature 35 }

		sensorTemperature36 OBJECT-TYPE
			SYNTAX INTEGER
			ACCESS read-only
			STATUS mandatory
			DESCRIPTION
				"Sensor temperature reading in tenths of degrees Celsius. Units:0.1   "
			::= { sensorStatusTemperature 36 }

		sensorTemperature37 OBJECT-TYPE
			SYNTAX INTEGER
			ACCESS read-only
			STATUS mandatory
			DESCRIPTION
				"Sensor temperature reading in tenths of degrees Celsius. Units:0.1   "
			::= { sensorStatusTemperature 37 }

		sensorTemperature38 OBJECT-TYPE
			SYNTAX INTEGER
			ACCESS read-only
			STATUS mandatory
			DESCRIPTION
				"Sensor temperature reading in tenths of degrees Celsius. Units:0.1   "
			::= { sensorStatusTemperature 38 }

		sensorTemperature39 OBJECT-TYPE
			SYNTAX INTEGER
			ACCESS read-only
			STATUS mandatory
			DESCRIPTION
				"Sensor temperature reading in tenths of degrees Celsius. Units:0.1   "
			::= { sensorStatusTemperature 39 }

		sensorTemperature40 OBJECT-TYPE
			SYNTAX INTEGER
			ACCESS read-only
			STATUS mandatory
			DESCRIPTION
				"Sensor temperature reading in tenths of degrees Celsius. Units:0.1   "
			::= { sensorStatusTemperature 40 }

		sensorTemperature41 OBJECT-TYPE
			SYNTAX INTEGER
			ACCESS read-only
			STATUS mandatory
			DESCRIPTION
				"Sensor temperature reading in tenths of degrees Celsius. Units:0.1   "
			::= { sensorStatusTemperature 41 }

		sensorTemperature42 OBJECT-TYPE
			SYNTAX INTEGER
			ACCESS read-only
			STATUS mandatory
			DESCRIPTION
				"Sensor temperature reading in tenths of degrees Celsius. Units:0.1   "
			::= { sensorStatusTemperature 42 }

		sensorTemperature43 OBJECT-TYPE
			SYNTAX INTEGER
			ACCESS read-only
			STATUS mandatory
			DESCRIPTION
				"Sensor temperature reading in tenths of degrees Celsius. Units:0.1   "
			::= { sensorStatusTemperature 43 }

		sensorTemperature44 OBJECT-TYPE
			SYNTAX INTEGER
			ACCESS read-only
			STATUS mandatory
			DESCRIPTION
				"Sensor temperature reading in tenths of degrees Celsius. Units:0.1   "
			::= { sensorStatusTemperature 44 }

		sensorTemperature45 OBJECT-TYPE
			SYNTAX INTEGER
			ACCESS read-only
			STATUS mandatory
			DESCRIPTION
				"Sensor temperature reading in tenths of degrees Celsius. Units:0.1   "
			::= { sensorStatusTemperature 45 }

		sensorTemperature46 OBJECT-TYPE
			SYNTAX INTEGER
			ACCESS read-only
			STATUS mandatory
			DESCRIPTION
				"Sensor temperature reading in tenths of degrees Celsius. Units:0.1   "
			::= { sensorStatusTemperature 46 }

		sensorTemperature47 OBJECT-TYPE
			SYNTAX INTEGER
			ACCESS read-only
			STATUS mandatory
			DESCRIPTION
				"Sensor temperature reading in tenths of degrees Celsius. Units:0.1   "
			::= { sensorStatusTemperature 47 }

		sensorTemperature48 OBJECT-TYPE
			SYNTAX INTEGER
			ACCESS read-only
			STATUS mandatory
			DESCRIPTION
				"Sensor temperature reading in tenths of degrees Celsius. Units:0.1   "
			::= { sensorStatusTemperature 48 }

		sensorTemperature49 OBJECT-TYPE
			SYNTAX INTEGER
			ACCESS read-only
			STATUS mandatory
			DESCRIPTION
				"Sensor temperature reading in tenths of degrees Celsius. Units:0.1   "
			::= { sensorStatusTemperature 49 }

		sensorTemperature50 OBJECT-TYPE
			SYNTAX INTEGER
			ACCESS read-only
			STATUS mandatory
			DESCRIPTION
				"Sensor temperature reading in tenths of degrees Celsius. Units:0.1   "
			::= { sensorStatusTemperature 50 }

		sensorTemperature51 OBJECT-TYPE
			SYNTAX INTEGER
			ACCESS read-only
			STATUS mandatory
			DESCRIPTION
				"Sensor temperature reading in tenths of degrees Celsius. Units:0.1   "
			::= { sensorStatusTemperature 51 }

		sensorTemperature52 OBJECT-TYPE
			SYNTAX INTEGER
			ACCESS read-only
			STATUS mandatory
			DESCRIPTION
				"Sensor temperature reading in tenths of degrees Celsius. Units:0.1   "
			::= { sensorStatusTemperature 52 }

		sensorTemperature53 OBJECT-TYPE
			SYNTAX INTEGER
			ACCESS read-only
			STATUS mandatory
			DESCRIPTION
				"Sensor temperature reading in tenths of degrees Celsius. Units:0.1   "
			::= { sensorStatusTemperature 53 }

		sensorTemperature54 OBJECT-TYPE
			SYNTAX INTEGER
			ACCESS read-only
			STATUS mandatory
			DESCRIPTION
				"Sensor temperature reading in tenths of degrees Celsius. Units:0.1   "
			::= { sensorStatusTemperature 54 }

		sensorTemperature55 OBJECT-TYPE
			SYNTAX INTEGER
			ACCESS read-only
			STATUS mandatory
			DESCRIPTION
				"Sensor temperature reading in tenths of degrees Celsius. Units:0.1   "
			::= { sensorStatusTemperature 55 }

		sensorTemperature56 OBJECT-TYPE
			SYNTAX INTEGER
			ACCESS read-only
			STATUS mandatory
			DESCRIPTION
				"Sensor temperature reading in tenths of degrees Celsius. Units:0.1   "
			::= { sensorStatusTemperature 56 }

		sensorTemperature57 OBJECT-TYPE
			SYNTAX INTEGER
			ACCESS read-only
			STATUS mandatory
			DESCRIPTION
				"Sensor temperature reading in tenths of degrees Celsius. Units:0.1   "
			::= { sensorStatusTemperature 57 }

		sensorTemperature58 OBJECT-TYPE
			SYNTAX INTEGER
			ACCESS read-only
			STATUS mandatory
			DESCRIPTION
				"Sensor temperature reading in tenths of degrees Celsius. Units:0.1   "
			::= { sensorStatusTemperature 58 }

		sensorTemperature59 OBJECT-TYPE
			SYNTAX INTEGER
			ACCESS read-only
			STATUS mandatory
			DESCRIPTION
				"Sensor temperature reading in tenths of degrees Celsius. Units:0.1   "
			::= { sensorStatusTemperature 59 }

		sensorTemperature60 OBJECT-TYPE
			SYNTAX INTEGER
			ACCESS read-only
			STATUS mandatory
			DESCRIPTION
				"Sensor temperature reading in tenths of degrees Celsius. Units:0.1   "
			::= { sensorStatusTemperature 60 }

		sensorTemperature61 OBJECT-TYPE
			SYNTAX INTEGER
			ACCESS read-only
			STATUS mandatory
			DESCRIPTION
				"Sensor temperature reading in tenths of degrees Celsius. Units:0.1   "
			::= { sensorStatusTemperature 61 }

		sensorTemperature62 OBJECT-TYPE
			SYNTAX INTEGER
			ACCESS read-only
			STATUS mandatory
			DESCRIPTION
				"Sensor temperature reading in tenths of degrees Celsius. Units:0.1   "
			::= { sensorStatusTemperature 62 }

		sensorTemperature63 OBJECT-TYPE
			SYNTAX INTEGER
			ACCESS read-only
			STATUS mandatory
			DESCRIPTION
				"Sensor temperature reading in tenths of degrees Celsius. Units:0.1   "
			::= { sensorStatusTemperature 63 }

		sensorTemperature64 OBJECT-TYPE
			SYNTAX INTEGER
			ACCESS read-only
			STATUS mandatory
			DESCRIPTION
				"Sensor temperature reading in tenths of degrees Celsius. Units:0.1   "
			::= { sensorStatusTemperature 64 }

		sensorTemperature65 OBJECT-TYPE
			SYNTAX INTEGER
			ACCESS read-only
			STATUS mandatory
			DESCRIPTION
				"Sensor temperature reading in tenths of degrees Celsius. Units:0.1   "
			::= { sensorStatusTemperature 65 }

		sensorTemperature66 OBJECT-TYPE
			SYNTAX INTEGER
			ACCESS read-only
			STATUS mandatory
			DESCRIPTION
				"Sensor temperature reading in tenths of degrees Celsius. Units:0.1   "
			::= { sensorStatusTemperature 66 }

		sensorTemperature67 OBJECT-TYPE
			SYNTAX INTEGER
			ACCESS read-only
			STATUS mandatory
			DESCRIPTION
				"Sensor temperature reading in tenths of degrees Celsius. Units:0.1   "
			::= { sensorStatusTemperature 67 }

		sensorTemperature68 OBJECT-TYPE
			SYNTAX INTEGER
			ACCESS read-only
			STATUS mandatory
			DESCRIPTION
				"Sensor temperature reading in tenths of degrees Celsius. Units:0.1   "
			::= { sensorStatusTemperature 68 }

		sensorTemperature69 OBJECT-TYPE
			SYNTAX INTEGER
			ACCESS read-only
			STATUS mandatory
			DESCRIPTION
				"Sensor temperature reading in tenths of degrees Celsius. Units:0.1   "
			::= { sensorStatusTemperature 69 }

		sensorTemperature70 OBJECT-TYPE
			SYNTAX INTEGER
			ACCESS read-only
			STATUS mandatory
			DESCRIPTION
				"Sensor temperature reading in tenths of degrees Celsius. Units:0.1   "
			::= { sensorStatusTemperature 70 }

		sensorTemperature71 OBJECT-TYPE
			SYNTAX INTEGER
			ACCESS read-only
			STATUS mandatory
			DESCRIPTION
				"Sensor temperature reading in tenths of degrees Celsius. Units:0.1   "
			::= { sensorStatusTemperature 71 }

		sensorTemperature72 OBJECT-TYPE
			SYNTAX INTEGER
			ACCESS read-only
			STATUS mandatory
			DESCRIPTION
				"Sensor temperature reading in tenths of degrees Celsius. Units:0.1   "
			::= { sensorStatusTemperature 72 }

		sensorTemperature73 OBJECT-TYPE
			SYNTAX INTEGER
			ACCESS read-only
			STATUS mandatory
			DESCRIPTION
				"Sensor temperature reading in tenths of degrees Celsius. Units:0.1   "
			::= { sensorStatusTemperature 73 }

		sensorTemperature74 OBJECT-TYPE
			SYNTAX INTEGER
			ACCESS read-only
			STATUS mandatory
			DESCRIPTION
				"Sensor temperature reading in tenths of degrees Celsius. Units:0.1   "
			::= { sensorStatusTemperature 74 }

		sensorTemperature75 OBJECT-TYPE
			SYNTAX INTEGER
			ACCESS read-only
			STATUS mandatory
			DESCRIPTION
				"Sensor temperature reading in tenths of degrees Celsius. Units:0.1   "
			::= { sensorStatusTemperature 75 }

		sensorTemperature76 OBJECT-TYPE
			SYNTAX INTEGER
			ACCESS read-only
			STATUS mandatory
			DESCRIPTION
				"Sensor temperature reading in tenths of degrees Celsius. Units:0.1   "
			::= { sensorStatusTemperature 76 }

		sensorTemperature77 OBJECT-TYPE
			SYNTAX INTEGER
			ACCESS read-only
			STATUS mandatory
			DESCRIPTION
				"Sensor temperature reading in tenths of degrees Celsius. Units:0.1   "
			::= { sensorStatusTemperature 77 }

		sensorTemperature78 OBJECT-TYPE
			SYNTAX INTEGER
			ACCESS read-only
			STATUS mandatory
			DESCRIPTION
				"Sensor temperature reading in tenths of degrees Celsius. Units:0.1   "
			::= { sensorStatusTemperature 78 }

		sensorTemperature79 OBJECT-TYPE
			SYNTAX INTEGER
			ACCESS read-only
			STATUS mandatory
			DESCRIPTION
				"Sensor temperature reading in tenths of degrees Celsius. Units:0.1   "
			::= { sensorStatusTemperature 79 }

		sensorTemperature80 OBJECT-TYPE
			SYNTAX INTEGER
			ACCESS read-only
			STATUS mandatory
			DESCRIPTION
				"Sensor temperature reading in tenths of degrees Celsius. Units:0.1   "
			::= { sensorStatusTemperature 80 }

		sensorTemperature81 OBJECT-TYPE
			SYNTAX INTEGER
			ACCESS read-only
			STATUS mandatory
			DESCRIPTION
				"Sensor temperature reading in tenths of degrees Celsius. Units:0.1   "
			::= { sensorStatusTemperature 81 }

		sensorTemperature82 OBJECT-TYPE
			SYNTAX INTEGER
			ACCESS read-only
			STATUS mandatory
			DESCRIPTION
				"Sensor temperature reading in tenths of degrees Celsius. Units:0.1   "
			::= { sensorStatusTemperature 82 }

		sensorTemperature83 OBJECT-TYPE
			SYNTAX INTEGER
			ACCESS read-only
			STATUS mandatory
			DESCRIPTION
				"Sensor temperature reading in tenths of degrees Celsius. Units:0.1   "
			::= { sensorStatusTemperature 83 }


		sensorTemperature84 OBJECT-TYPE
			SYNTAX INTEGER
			ACCESS read-only
			STATUS mandatory
			DESCRIPTION
				"Sensor temperature reading in tenths of degrees Celsius. Units:0.1   "
			::= { sensorStatusTemperature 84 }

		sensorTemperature85 OBJECT-TYPE
			SYNTAX INTEGER
			ACCESS read-only
			STATUS mandatory
			DESCRIPTION
				"Sensor temperature reading in tenths of degrees Celsius. Units:0.1   "
			::= { sensorStatusTemperature 85 }

		sensorTemperature86 OBJECT-TYPE
			SYNTAX INTEGER
			ACCESS read-only
			STATUS mandatory
			DESCRIPTION
				"Sensor temperature reading in tenths of degrees Celsius. Units:0.1   "
			::= { sensorStatusTemperature 86 }

		sensorTemperature87 OBJECT-TYPE
			SYNTAX INTEGER
			ACCESS read-only
			STATUS mandatory
			DESCRIPTION
				"Sensor temperature reading in tenths of degrees Celsius. Units:0.1   "
			::= { sensorStatusTemperature 87 }

		sensorTemperature88 OBJECT-TYPE
			SYNTAX INTEGER
			ACCESS read-only
			STATUS mandatory
			DESCRIPTION
				"Sensor temperature reading in tenths of degrees Celsius. Units:0.1   "
			::= { sensorStatusTemperature 88 }

		sensorTemperature89 OBJECT-TYPE
			SYNTAX INTEGER
			ACCESS read-only
			STATUS mandatory
			DESCRIPTION
				"Sensor temperature reading in tenths of degrees Celsius. Units:0.1   "
			::= { sensorStatusTemperature 89 }

		sensorTemperature90 OBJECT-TYPE
			SYNTAX INTEGER
			ACCESS read-only
			STATUS mandatory
			DESCRIPTION
				"Sensor temperature reading in tenths of degrees Celsius. Units:0.1   "
			::= { sensorStatusTemperature 90 }

		sensorTemperature91 OBJECT-TYPE
			SYNTAX INTEGER
			ACCESS read-only
			STATUS mandatory
			DESCRIPTION
				"Sensor temperature reading in tenths of degrees Celsius. Units:0.1   "
			::= { sensorStatusTemperature 91 }

		sensorTemperature92 OBJECT-TYPE
			SYNTAX INTEGER
			ACCESS read-only
			STATUS mandatory
			DESCRIPTION
				"Sensor temperature reading in tenths of degrees Celsius. Units:0.1   "
			::= { sensorStatusTemperature 92 }

		sensorTemperature93 OBJECT-TYPE
			SYNTAX INTEGER
			ACCESS read-only
			STATUS mandatory
			DESCRIPTION
				"Sensor temperature reading in tenths of degrees Celsius. Units:0.1   "
			::= { sensorStatusTemperature 93 }

		sensorTemperature94 OBJECT-TYPE
			SYNTAX INTEGER
			ACCESS read-only
			STATUS mandatory
			DESCRIPTION
				"Sensor temperature reading in tenths of degrees Celsius. Units:0.1   "
			::= { sensorStatusTemperature 94 }

		sensorTemperature95 OBJECT-TYPE
			SYNTAX INTEGER
			ACCESS read-only
			STATUS mandatory
			DESCRIPTION
				"Sensor temperature reading in tenths of degrees Celsius. Units:0.1   "
			::= { sensorStatusTemperature 95 }

		sensorTemperature96 OBJECT-TYPE
			SYNTAX INTEGER
			ACCESS read-only
			STATUS mandatory
			DESCRIPTION
				"Sensor temperature reading in tenths of degrees Celsius. Units:0.1   "
			::= { sensorStatusTemperature 96 }



		-- 1.3.6.1.4.1.23280.12.1.3
		sensorStatusHumidity OBJECT-TYPE
			SYNTAX INTEGER
			ACCESS read-only
			STATUS mandatory
			DESCRIPTION
				"Sensor humidity reading in percent relative humidity. Units:0.1% RH"
			::= { sensorStatusEntry 3 }

		sensorHumidity1 OBJECT-TYPE
			SYNTAX INTEGER
			ACCESS read-only
			STATUS mandatory
			DESCRIPTION
				"Sensor humidity reading in percent relative humidity. Units:0.1% RH"
			::= { sensorStatusHumidity 1 }

		sensorHumidity2 OBJECT-TYPE
			SYNTAX INTEGER
			ACCESS read-only
			STATUS mandatory
			DESCRIPTION
				"Sensor humidity reading in percent relative humidity. Units:0.1% RH"
			::= { sensorStatusHumidity 2 }

		sensorHumidity3 OBJECT-TYPE
			SYNTAX INTEGER
			ACCESS read-only
			STATUS mandatory
			DESCRIPTION
				"Sensor humidity reading in percent relative humidity. Units:0.1% RH"
			::= { sensorStatusHumidity 3 }

		sensorHumidity4 OBJECT-TYPE
			SYNTAX INTEGER
			ACCESS read-only
			STATUS mandatory
			DESCRIPTION
				"Sensor humidity reading in percent relative humidity. Units:0.1% RH"
			::= { sensorStatusHumidity 4 }

		sensorHumidity5 OBJECT-TYPE
			SYNTAX INTEGER
			ACCESS read-only
			STATUS mandatory
			DESCRIPTION
				"Sensor humidity reading in percent relative humidity. Units:0.1% RH"
			::= { sensorStatusHumidity 5 }

		sensorHumidity6 OBJECT-TYPE
			SYNTAX INTEGER
			ACCESS read-only
			STATUS mandatory
			DESCRIPTION
				"Sensor humidity reading in percent relative humidity. Units:0.1% RH"
			::= { sensorStatusHumidity 6 }

		sensorHumidity7 OBJECT-TYPE
			SYNTAX INTEGER
			ACCESS read-only
			STATUS mandatory
			DESCRIPTION
				"Sensor humidity reading in percent relative humidity. Units:0.1% RH"
			::= { sensorStatusHumidity 7 }

		sensorHumidity8 OBJECT-TYPE
			SYNTAX INTEGER
			ACCESS read-only
			STATUS mandatory
			DESCRIPTION
				"Sensor humidity reading in percent relative humidity. Units:0.1% RH"
			::= { sensorStatusHumidity 8 }

		sensorHumidity9 OBJECT-TYPE
			SYNTAX INTEGER
			ACCESS read-only
			STATUS mandatory
			DESCRIPTION
				"Sensor humidity reading in percent relative humidity. Units:0.1% RH"
			::= { sensorStatusHumidity 9 }

		sensorHumidity10 OBJECT-TYPE
			SYNTAX INTEGER
			ACCESS read-only
			STATUS mandatory
			DESCRIPTION
				"Sensor humidity reading in percent relative humidity. Units:0.1% RH"
			::= { sensorStatusHumidity 10 }

		sensorHumidity11 OBJECT-TYPE
			SYNTAX INTEGER
			ACCESS read-only
			STATUS mandatory
			DESCRIPTION
				"Sensor humidity reading in percent relative humidity. Units:0.1% RH"
			::= { sensorStatusHumidity 11 }

		sensorHumidity12 OBJECT-TYPE
			SYNTAX INTEGER
			ACCESS read-only
			STATUS mandatory
			DESCRIPTION
				"Sensor humidity reading in percent relative humidity. Units:0.1% RH"
			::= { sensorStatusHumidity 12 }

		sensorHumidity13 OBJECT-TYPE
			SYNTAX INTEGER
			ACCESS read-only
			STATUS mandatory
			DESCRIPTION
				"Sensor humidity reading in percent relative humidity. Units:0.1% RH"
			::= { sensorStatusHumidity 13 }

		sensorHumidity14 OBJECT-TYPE
			SYNTAX INTEGER
			ACCESS read-only
			STATUS mandatory
			DESCRIPTION
				"Sensor humidity reading in percent relative humidity. Units:0.1% RH"
			::= { sensorStatusHumidity 14 }

		sensorHumidity15 OBJECT-TYPE
			SYNTAX INTEGER
			ACCESS read-only
			STATUS mandatory
			DESCRIPTION
				"Sensor humidity reading in percent relative humidity. Units:0.1% RH"
			::= { sensorStatusHumidity 15 }

		sensorHumidity16 OBJECT-TYPE
			SYNTAX INTEGER
			ACCESS read-only
			STATUS mandatory
			DESCRIPTION
				"Sensor humidity reading in percent relative humidity. Units:0.1% RH"
			::= { sensorStatusHumidity 16 }

		sensorHumidity17 OBJECT-TYPE
			SYNTAX INTEGER
			ACCESS read-only
			STATUS mandatory
			DESCRIPTION
				"Sensor humidity reading in percent relative humidity. Units:0.1% RH"
			::= { sensorStatusHumidity 17 }

		sensorHumidity18 OBJECT-TYPE
			SYNTAX INTEGER
			ACCESS read-only
			STATUS mandatory
			DESCRIPTION
				"Sensor humidity reading in percent relative humidity. Units:0.1% RH"
			::= { sensorStatusHumidity 18 }

		sensorHumidity19 OBJECT-TYPE
			SYNTAX INTEGER
			ACCESS read-only
			STATUS mandatory
			DESCRIPTION
				"Sensor humidity reading in percent relative humidity. Units:0.1% RH"
			::= { sensorStatusHumidity 19 }

		sensorHumidity20 OBJECT-TYPE
			SYNTAX INTEGER
			ACCESS read-only
			STATUS mandatory
			DESCRIPTION
				"Sensor humidity reading in percent relative humidity. Units:0.1% RH"
			::= { sensorStatusHumidity 20 }


		sensorHumidity21 OBJECT-TYPE
			SYNTAX INTEGER
			ACCESS read-only
			STATUS mandatory
			DESCRIPTION
				"Sensor humidity reading in percent relative humidity. Units:0.1% RH"
			::= { sensorStatusHumidity 21 }

		sensorHumidity22 OBJECT-TYPE
			SYNTAX INTEGER
			ACCESS read-only
			STATUS mandatory
			DESCRIPTION
				"Sensor humidity reading in percent relative humidity. Units:0.1% RH"
			::= { sensorStatusHumidity 22 }

		sensorHumidity23 OBJECT-TYPE
			SYNTAX INTEGER
			ACCESS read-only
			STATUS mandatory
			DESCRIPTION
				"Sensor humidity reading in percent relative humidity. Units:0.1% RH"
			::= { sensorStatusHumidity 23 }

		sensorHumidity24 OBJECT-TYPE
			SYNTAX INTEGER
			ACCESS read-only
			STATUS mandatory
			DESCRIPTION
				"Sensor humidity reading in percent relative humidity. Units:0.1% RH"
			::= { sensorStatusHumidity 24 }

		sensorHumidity25 OBJECT-TYPE
			SYNTAX INTEGER
			ACCESS read-only
			STATUS mandatory
			DESCRIPTION
				"Sensor humidity reading in percent relative humidity. Units:0.1% RH"
			::= { sensorStatusHumidity 25 }

		sensorHumidity26 OBJECT-TYPE
			SYNTAX INTEGER
			ACCESS read-only
			STATUS mandatory
			DESCRIPTION
				"Sensor humidity reading in percent relative humidity. Units:0.1% RH"
			::= { sensorStatusHumidity 26 }

		sensorHumidity27 OBJECT-TYPE
			SYNTAX INTEGER
			ACCESS read-only
			STATUS mandatory
			DESCRIPTION
				"Sensor humidity reading in percent relative humidity. Units:0.1% RH"
			::= { sensorStatusHumidity 27 }

		sensorHumidity28 OBJECT-TYPE
			SYNTAX INTEGER
			ACCESS read-only
			STATUS mandatory
			DESCRIPTION
				"Sensor humidity reading in percent relative humidity. Units:0.1% RH"
			::= { sensorStatusHumidity 28 }

		sensorHumidity29 OBJECT-TYPE
			SYNTAX INTEGER
			ACCESS read-only
			STATUS mandatory
			DESCRIPTION
				"Sensor humidity reading in percent relative humidity. Units:0.1% RH"
			::= { sensorStatusHumidity 29 }

		sensorHumidity30 OBJECT-TYPE
			SYNTAX INTEGER
			ACCESS read-only
			STATUS mandatory
			DESCRIPTION
				"Sensor humidity reading in percent relative humidity. Units:0.1% RH"
			::= { sensorStatusHumidity 30 }

		sensorHumidity31 OBJECT-TYPE
			SYNTAX INTEGER
			ACCESS read-only
			STATUS mandatory
			DESCRIPTION
				"Sensor humidity reading in percent relative humidity. Units:0.1% RH"
			::= { sensorStatusHumidity 31 }

		sensorHumidity32 OBJECT-TYPE
			SYNTAX INTEGER
			ACCESS read-only
			STATUS mandatory
			DESCRIPTION
				"Sensor humidity reading in percent relative humidity. Units:0.1% RH"
			::= { sensorStatusHumidity 32 }

		sensorHumidity33 OBJECT-TYPE
			SYNTAX INTEGER
			ACCESS read-only
			STATUS mandatory
			DESCRIPTION
				"Sensor humidity reading in percent relative humidity. Units:0.1% RH"
			::= { sensorStatusHumidity 33 }

		sensorHumidity34 OBJECT-TYPE
			SYNTAX INTEGER
			ACCESS read-only
			STATUS mandatory
			DESCRIPTION
				"Sensor humidity reading in percent relative humidity. Units:0.1% RH"
			::= { sensorStatusHumidity 34 }

		sensorHumidity35 OBJECT-TYPE
			SYNTAX INTEGER
			ACCESS read-only
			STATUS mandatory
			DESCRIPTION
				"Sensor humidity reading in percent relative humidity. Units:0.1% RH"
			::= { sensorStatusHumidity 35 }

		sensorHumidity36 OBJECT-TYPE
			SYNTAX INTEGER
			ACCESS read-only
			STATUS mandatory
			DESCRIPTION
				"Sensor humidity reading in percent relative humidity. Units:0.1% RH"
			::= { sensorStatusHumidity 36 }

		sensorHumidity37 OBJECT-TYPE
			SYNTAX INTEGER
			ACCESS read-only
			STATUS mandatory
			DESCRIPTION
				"Sensor humidity reading in percent relative humidity. Units:0.1% RH"
			::= { sensorStatusHumidity 37 }

		sensorHumidity38 OBJECT-TYPE
			SYNTAX INTEGER
			ACCESS read-only
			STATUS mandatory
			DESCRIPTION
				"Sensor humidity reading in percent relative humidity. Units:0.1% RH"
			::= { sensorStatusHumidity 38 }

		sensorHumidity39 OBJECT-TYPE
			SYNTAX INTEGER
			ACCESS read-only
			STATUS mandatory
			DESCRIPTION
				"Sensor humidity reading in percent relative humidity. Units:0.1% RH"
			::= { sensorStatusHumidity 39 }

		sensorHumidity40 OBJECT-TYPE
			SYNTAX INTEGER
			ACCESS read-only
			STATUS mandatory
			DESCRIPTION
				"Sensor humidity reading in percent relative humidity. Units:0.1% RH"
			::= { sensorStatusHumidity 40 }

		sensorHumidity41 OBJECT-TYPE
			SYNTAX INTEGER
			ACCESS read-only
			STATUS mandatory
			DESCRIPTION
				"Sensor humidity reading in percent relative humidity. Units:0.1% RH"
			::= { sensorStatusHumidity 41 }

		sensorHumidity42 OBJECT-TYPE
			SYNTAX INTEGER
			ACCESS read-only
			STATUS mandatory
			DESCRIPTION
				"Sensor humidity reading in percent relative humidity. Units:0.1% RH"
			::= { sensorStatusHumidity 42 }

		sensorHumidity43 OBJECT-TYPE
			SYNTAX INTEGER
			ACCESS read-only
			STATUS mandatory
			DESCRIPTION
				"Sensor humidity reading in percent relative humidity. Units:0.1% RH"
			::= { sensorStatusHumidity 43 }

		sensorHumidity44 OBJECT-TYPE
			SYNTAX INTEGER
			ACCESS read-only
			STATUS mandatory
			DESCRIPTION
				"Sensor humidity reading in percent relative humidity. Units:0.1% RH"
			::= { sensorStatusHumidity 44 }

		sensorHumidity45 OBJECT-TYPE
			SYNTAX INTEGER
			ACCESS read-only
			STATUS mandatory
			DESCRIPTION
				"Sensor humidity reading in percent relative humidity. Units:0.1% RH"
			::= { sensorStatusHumidity 45 }

		sensorHumidity46 OBJECT-TYPE
			SYNTAX INTEGER
			ACCESS read-only
			STATUS mandatory
			DESCRIPTION
				"Sensor humidity reading in percent relative humidity. Units:0.1% RH"
			::= { sensorStatusHumidity 46 }

		sensorHumidity47 OBJECT-TYPE
			SYNTAX INTEGER
			ACCESS read-only
			STATUS mandatory
			DESCRIPTION
				"Sensor humidity reading in percent relative humidity. Units:0.1% RH"
			::= { sensorStatusHumidity 47 }

		sensorHumidity48 OBJECT-TYPE
			SYNTAX INTEGER
			ACCESS read-only
			STATUS mandatory
			DESCRIPTION
				"Sensor humidity reading in percent relative humidity. Units:0.1% RH"
			::= { sensorStatusHumidity 48 }

		sensorHumidity49 OBJECT-TYPE
			SYNTAX INTEGER
			ACCESS read-only
			STATUS mandatory
			DESCRIPTION
				"Sensor humidity reading in percent relative humidity. Units:0.1% RH"
			::= { sensorStatusHumidity 49 }

		sensorHumidity50 OBJECT-TYPE
			SYNTAX INTEGER
			ACCESS read-only
			STATUS mandatory
			DESCRIPTION
				"Sensor humidity reading in percent relative humidity. Units:0.1% RH"
			::= { sensorStatusHumidity 50 }

		sensorHumidity51 OBJECT-TYPE
			SYNTAX INTEGER
			ACCESS read-only
			STATUS mandatory
			DESCRIPTION
				"Sensor humidity reading in percent relative humidity. Units:0.1% RH"
			::= { sensorStatusHumidity 51 }

		sensorHumidity52 OBJECT-TYPE
			SYNTAX INTEGER
			ACCESS read-only
			STATUS mandatory
			DESCRIPTION
				"Sensor humidity reading in percent relative humidity. Units:0.1% RH"
			::= { sensorStatusHumidity 52 }

		sensorHumidity53 OBJECT-TYPE
			SYNTAX INTEGER
			ACCESS read-only
			STATUS mandatory
			DESCRIPTION
				"Sensor humidity reading in percent relative humidity. Units:0.1% RH"
			::= { sensorStatusHumidity 53 }

		sensorHumidity54 OBJECT-TYPE
			SYNTAX INTEGER
			ACCESS read-only
			STATUS mandatory
			DESCRIPTION
				"Sensor humidity reading in percent relative humidity. Units:0.1% RH"
			::= { sensorStatusHumidity 54 }

		sensorHumidity55 OBJECT-TYPE
			SYNTAX INTEGER
			ACCESS read-only
			STATUS mandatory
			DESCRIPTION
				"Sensor humidity reading in percent relative humidity. Units:0.1% RH"
			::= { sensorStatusHumidity 55 }

		sensorHumidity56 OBJECT-TYPE
			SYNTAX INTEGER
			ACCESS read-only
			STATUS mandatory
			DESCRIPTION
				"Sensor humidity reading in percent relative humidity. Units:0.1% RH"
			::= { sensorStatusHumidity 56 }

		sensorHumidity57 OBJECT-TYPE
			SYNTAX INTEGER
			ACCESS read-only
			STATUS mandatory
			DESCRIPTION
				"Sensor humidity reading in percent relative humidity. Units:0.1% RH"
			::= { sensorStatusHumidity 57 }

		sensorHumidity58 OBJECT-TYPE
			SYNTAX INTEGER
			ACCESS read-only
			STATUS mandatory
			DESCRIPTION
				"Sensor humidity reading in percent relative humidity. Units:0.1% RH"
			::= { sensorStatusHumidity 58 }

		sensorHumidity59 OBJECT-TYPE
			SYNTAX INTEGER
			ACCESS read-only
			STATUS mandatory
			DESCRIPTION
				"Sensor humidity reading in percent relative humidity. Units:0.1% RH"
			::= { sensorStatusHumidity 59 }

		sensorHumidity60 OBJECT-TYPE
			SYNTAX INTEGER
			ACCESS read-only
			STATUS mandatory
			DESCRIPTION
				"Sensor humidity reading in percent relative humidity. Units:0.1% RH"
			::= { sensorStatusHumidity 60 }

		sensorHumidity61 OBJECT-TYPE
			SYNTAX INTEGER
			ACCESS read-only
			STATUS mandatory
			DESCRIPTION
				"Sensor humidity reading in percent relative humidity. Units:0.1% RH"
			::= { sensorStatusHumidity 61 }

		sensorHumidity62 OBJECT-TYPE
			SYNTAX INTEGER
			ACCESS read-only
			STATUS mandatory
			DESCRIPTION
				"Sensor humidity reading in percent relative humidity. Units:0.1% RH"
			::= { sensorStatusHumidity 62 }

		sensorHumidity63 OBJECT-TYPE
			SYNTAX INTEGER
			ACCESS read-only
			STATUS mandatory
			DESCRIPTION
				"Sensor humidity reading in percent relative humidity. Units:0.1% RH"
			::= { sensorStatusHumidity 63 }

		sensorHumidity64 OBJECT-TYPE
			SYNTAX INTEGER
			ACCESS read-only
			STATUS mandatory
			DESCRIPTION
				"Sensor humidity reading in percent relative humidity. Units:0.1% RH"
			::= { sensorStatusHumidity 64 }

		sensorHumidity65 OBJECT-TYPE
			SYNTAX INTEGER
			ACCESS read-only
			STATUS mandatory
			DESCRIPTION
				"Sensor humidity reading in percent relative humidity. Units:0.1% RH"
			::= { sensorStatusHumidity 65 }

		sensorHumidity66 OBJECT-TYPE
			SYNTAX INTEGER
			ACCESS read-only
			STATUS mandatory
			DESCRIPTION
				"Sensor humidity reading in percent relative humidity. Units:0.1% RH"
			::= { sensorStatusHumidity 66 }

		sensorHumidity67 OBJECT-TYPE
			SYNTAX INTEGER
			ACCESS read-only
			STATUS mandatory
			DESCRIPTION
				"Sensor humidity reading in percent relative humidity. Units:0.1% RH"
			::= { sensorStatusHumidity 67 }

		sensorHumidity68 OBJECT-TYPE
			SYNTAX INTEGER
			ACCESS read-only
			STATUS mandatory
			DESCRIPTION
				"Sensor humidity reading in percent relative humidity. Units:0.1% RH"
			::= { sensorStatusHumidity 68 }

		sensorHumidity69 OBJECT-TYPE
			SYNTAX INTEGER
			ACCESS read-only
			STATUS mandatory
			DESCRIPTION
				"Sensor humidity reading in percent relative humidity. Units:0.1% RH"
			::= { sensorStatusHumidity 69 }

		sensorHumidity70 OBJECT-TYPE
			SYNTAX INTEGER
			ACCESS read-only
			STATUS mandatory
			DESCRIPTION
				"Sensor humidity reading in percent relative humidity. Units:0.1% RH"
			::= { sensorStatusHumidity 70 }

		sensorHumidity71 OBJECT-TYPE
			SYNTAX INTEGER
			ACCESS read-only
			STATUS mandatory
			DESCRIPTION
				"Sensor humidity reading in percent relative humidity. Units:0.1% RH"
			::= { sensorStatusHumidity 71 }

		sensorHumidity72 OBJECT-TYPE
			SYNTAX INTEGER
			ACCESS read-only
			STATUS mandatory
			DESCRIPTION
				"Sensor humidity reading in percent relative humidity. Units:0.1% RH"
			::= { sensorStatusHumidity 72 }

		sensorHumidity73 OBJECT-TYPE
			SYNTAX INTEGER
			ACCESS read-only
			STATUS mandatory
			DESCRIPTION
				"Sensor humidity reading in percent relative humidity. Units:0.1% RH"
			::= { sensorStatusHumidity 73 }

		sensorHumidity74 OBJECT-TYPE
			SYNTAX INTEGER
			ACCESS read-only
			STATUS mandatory
			DESCRIPTION
				"Sensor humidity reading in percent relative humidity. Units:0.1% RH"
			::= { sensorStatusHumidity 74 }

		sensorHumidity75 OBJECT-TYPE
			SYNTAX INTEGER
			ACCESS read-only
			STATUS mandatory
			DESCRIPTION
				"Sensor humidity reading in percent relative humidity. Units:0.1% RH"
			::= { sensorStatusHumidity 75 }

		sensorHumidity76 OBJECT-TYPE
			SYNTAX INTEGER
			ACCESS read-only
			STATUS mandatory
			DESCRIPTION
				"Sensor humidity reading in percent relative humidity. Units:0.1% RH"
			::= { sensorStatusHumidity 76 }

		sensorHumidity77 OBJECT-TYPE
			SYNTAX INTEGER
			ACCESS read-only
			STATUS mandatory
			DESCRIPTION
				"Sensor humidity reading in percent relative humidity. Units:0.1% RH"
			::= { sensorStatusHumidity 77 }

		sensorHumidity78 OBJECT-TYPE
			SYNTAX INTEGER
			ACCESS read-only
			STATUS mandatory
			DESCRIPTION
				"Sensor humidity reading in percent relative humidity. Units:0.1% RH"
			::= { sensorStatusHumidity 78 }

		sensorHumidity79 OBJECT-TYPE
			SYNTAX INTEGER
			ACCESS read-only
			STATUS mandatory
			DESCRIPTION
				"Sensor humidity reading in percent relative humidity. Units:0.1% RH"
			::= { sensorStatusHumidity 79 }

		sensorHumidity80 OBJECT-TYPE
			SYNTAX INTEGER
			ACCESS read-only
			STATUS mandatory
			DESCRIPTION
				"Sensor humidity reading in percent relative humidity. Units:0.1% RH"
			::= { sensorStatusHumidity 80 }

		sensorHumidity81 OBJECT-TYPE
			SYNTAX INTEGER
			ACCESS read-only
			STATUS mandatory
			DESCRIPTION
				"Sensor humidity reading in percent relative humidity. Units:0.1% RH"
			::= { sensorStatusHumidity 81 }

		sensorHumidity82 OBJECT-TYPE
			SYNTAX INTEGER
			ACCESS read-only
			STATUS mandatory
			DESCRIPTION
				"Sensor humidity reading in percent relative humidity. Units:0.1% RH"
			::= { sensorStatusHumidity 82 }

		sensorHumidity83 OBJECT-TYPE
			SYNTAX INTEGER
			ACCESS read-only
			STATUS mandatory
			DESCRIPTION
				"Sensor humidity reading in percent relative humidity. Units:0.1% RH"
			::= { sensorStatusHumidity 83 }

		sensorHumidity84 OBJECT-TYPE
			SYNTAX INTEGER
			ACCESS read-only
			STATUS mandatory
			DESCRIPTION
				"Sensor humidity reading in percent relative humidity. Units:0.1% RH"
			::= { sensorStatusHumidity 84 }

		sensorHumidity85 OBJECT-TYPE
			SYNTAX INTEGER
			ACCESS read-only
			STATUS mandatory
			DESCRIPTION
				"Sensor humidity reading in percent relative humidity. Units:0.1% RH"
			::= { sensorStatusHumidity 85 }

		sensorHumidity86 OBJECT-TYPE
			SYNTAX INTEGER
			ACCESS read-only
			STATUS mandatory
			DESCRIPTION
				"Sensor humidity reading in percent relative humidity. Units:0.1% RH"
			::= { sensorStatusHumidity 86 }

		sensorHumidity87 OBJECT-TYPE
			SYNTAX INTEGER
			ACCESS read-only
			STATUS mandatory
			DESCRIPTION
				"Sensor humidity reading in percent relative humidity. Units:0.1% RH"
			::= { sensorStatusHumidity 87 }

		sensorHumidity88 OBJECT-TYPE
			SYNTAX INTEGER
			ACCESS read-only
			STATUS mandatory
			DESCRIPTION
				"Sensor humidity reading in percent relative humidity. Units:0.1% RH"
			::= { sensorStatusHumidity 88 }

		sensorHumidity89 OBJECT-TYPE
			SYNTAX INTEGER
			ACCESS read-only
			STATUS mandatory
			DESCRIPTION
				"Sensor humidity reading in percent relative humidity. Units:0.1% RH"
			::= { sensorStatusHumidity 89 }

		sensorHumidity90 OBJECT-TYPE
			SYNTAX INTEGER
			ACCESS read-only
			STATUS mandatory
			DESCRIPTION
				"Sensor humidity reading in percent relative humidity. Units:0.1% RH"
			::= { sensorStatusHumidity 90 }

		sensorHumidity91 OBJECT-TYPE
			SYNTAX INTEGER
			ACCESS read-only
			STATUS mandatory
			DESCRIPTION
				"Sensor humidity reading in percent relative humidity. Units:0.1% RH"
			::= { sensorStatusHumidity 91 }

		sensorHumidity92 OBJECT-TYPE
			SYNTAX INTEGER
			ACCESS read-only
			STATUS mandatory
			DESCRIPTION
				"Sensor humidity reading in percent relative humidity. Units:0.1% RH"
			::= { sensorStatusHumidity 92 }

		sensorHumidity93 OBJECT-TYPE
			SYNTAX INTEGER
			ACCESS read-only
			STATUS mandatory
			DESCRIPTION
				"Sensor humidity reading in percent relative humidity. Units:0.1% RH"
			::= { sensorStatusHumidity 93 }

		sensorHumidity94 OBJECT-TYPE
			SYNTAX INTEGER
			ACCESS read-only
			STATUS mandatory
			DESCRIPTION
				"Sensor humidity reading in percent relative humidity. Units:0.1% RH"
			::= { sensorStatusHumidity 94 }

		sensorHumidity95 OBJECT-TYPE
			SYNTAX INTEGER
			ACCESS read-only
			STATUS mandatory
			DESCRIPTION
				"Sensor humidity reading in percent relative humidity. Units:0.1% RH"
			::= { sensorStatusHumidity 95 }

		sensorHumidity96 OBJECT-TYPE
			SYNTAX INTEGER
			ACCESS read-only
			STATUS mandatory
			DESCRIPTION
				"Sensor humidity reading in percent relative humidity. Units:0.1% RH"
			::= { sensorStatusHumidity 96 }



		-- 1.3.6.1.4.1.23280.12.1.4
		sensorStatusTemperatureLimitState OBJECT-TYPE
			SYNTAX INTEGER
				{
				normal(1),
				upperLimit(2),
				lowerLimit(3)
				}
			ACCESS read-only
			STATUS mandatory
			DESCRIPTION
				"Indicates the Sensor temperature limit state.
				Normal(1) means that the limit is not exceeded. 
				upperLimit(2) is the upper limit, 
				and lowerLimit(3) is the lower limit."
			::= { sensorStatusEntry 4 }

		
		-- 1.3.6.1.4.1.23280.12.1.5
		sensorStatusHumidityLimitState OBJECT-TYPE
			SYNTAX INTEGER
				{
				normal(1),
				upperLimit(2),
				lowerLimit(3)
				}
			ACCESS read-only
			STATUS mandatory
			DESCRIPTION
				"Indicates the Sensor Humidity limit state.
				Normal(1) means that the limit is not exceeded. 
				upperLimit(2) is the upper limit, 
				and lowerLimit(3) is the lower limit."
			::= { sensorStatusEntry 5 }

		
		-- 1.3.6.1.4.1.23280.12.1.6
		sensorStatusIOSensorState OBJECT-TYPE
			SYNTAX INTEGER
				{
				normal(1),
				alarm(2)
				}
			ACCESS read-only
			STATUS mandatory
			DESCRIPTION
				"Indicates the IO Sensor state.
				Normal(1) means that the alarm is not exceeded. 
				Alarm(2) is the alarm  happen."
			::= { sensorStatusEntry 6 }

		
	
--
-- Trap definitions
--
	
		criticalCondition TRAP-TYPE 
			ENTERPRISE pdu
			VARIABLES { phaseStatusVoltage, phaseStatusCurrent, sensorStatusTemperature, sensorStatusHumidity, deviceStatusZeroLineCurrent, 
				deviceStatusThreePhaseUnbalance }
			DESCRIPTION 
				"SEVERE: A IPDU critical condition has been detected.
				The first variable is the device number.
				The second variable is the instance number.
				The third variable is the trap text message."
			::=  1

		criticalConditionCleared TRAP-TYPE 
			ENTERPRISE pdu
			VARIABLES { phaseStatusVoltage, phaseStatusCurrent, deviceStatusThreePhaseUnbalance, deviceStatusZeroLineCurrent, sensorStatusHumidity, 
				sensorStatusTemperature }
			DESCRIPTION 
				"INFORMATIONAL: A IPDU critical condition has been cleared.
				The first variable is the device number.
				The second variable is the instance number.
				The third variable is the trap text message."
			::=  2

		warningCondition TRAP-TYPE 
			ENTERPRISE pdu
			VARIABLES { phaseStatusVoltage, phaseStatusCurrent, sensorStatusHumidity, sensorStatusTemperature }
			DESCRIPTION 
				"SEVERE: A IPDU warnning condition has been detected.
				The first variable is the device number.
				The second variable is the instance number.
				The third variable is the trap text message."
			::=  3

		warningConditionCleared TRAP-TYPE 
			ENTERPRISE pdu
			VARIABLES { phaseStatusVoltage, phaseStatusCurrent, sensorStatusHumidity, sensorStatusTemperature }
			DESCRIPTION 
				"SEVERE: A IPDU warnning condition has been cleared.
				The first variable is the device number.
				The second variable is the instance number.
				The third variable is the trap text message."
			::=  4

	
	END

--
-- PDUMIBV07.my
--
